# INDEMNITY: By using this software you agree not to sue me for any reason related to the use of this software.
#
# Copyright (c) 2022 Kurt Funderburg, all rights not explicitly relinquished in LGPL reserved.
#
#   This program is free software; you can redistribute it and/or modify  
#   it under the terms of the GNU Lesser General Public License (LGPL)    
#   as published by the Free Software Foundation; either version 2 of     
#   the License, or (at your option) any later version.                   
#                                                                         
#   This program is distributed in the hope that it will be useful,       
#   but WITHOUT ANY WARRANTY; without even the implied warranty of       
#   MERCHANTABILITY or FITNESS FOR A PARTICULAR PURPOSE.  See the         
#   GNU Library General Public License for more details.                  
#                                                                         
#   You should have received a copy of the GNU Library General Public     
#   License along with this program; if not, write to the Free Software   
#   Foundation, Inc., 59 Temple Place, Suite 330, Boston, MA  02111-1307  
#   USA                                                                   
import FreeCAD, Part, math, os
from FreeCAD import Base
from AttachmentEditor import Commands
import ThreadMaker.TMClasses as TMClasses
from ThreadMaker.TMClasses import TMThreadInsert, TMThreadVP, INTOBJECTNAME

__title__="ThreadMaker MakeInsert Macro: Generates fully parametric custom or standardized threaded inserts."
__author__ = "Kurt Funderburg"

# Main Code 		#######################################################
TEST = False
doc = App.ActiveDocument

if not TEST:
	# Launch input dimensions dialog box
	threadspecs = TMClasses.TMDialog(True)
	threadspecs.exec()
	speclist = threadspecs.result
	# [Standard, Size, diameter, pitch, length, taper, clearance, chamfer(bool), left-handed(bool), thrddisable(bool), roundroot(bool), pitchtol, cresttol]

	if speclist:		# Make threaded shaft unless dialog cancelled
		doc.openTransaction("Make Thread Insert")
		a = doc.addObject("Part::FeaturePython", INTOBJECTNAME, None, None, False)
		doc.commitTransaction()
		TMThreadInsert(a, speclist)			# Build Thread object with speclist
		TMThreadVP(a.ViewObject)		# Build View Provider
		a.setEditorMode('Placement', 0) #non-readonly non-hidden
